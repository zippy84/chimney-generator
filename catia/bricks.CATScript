' man muss auf einer fläche eine skizze mit genau zwei punkten erstellen, die ein rechteck aufspannen
' die skizze auswählen und unter Tools -> Makros... das script hier ausführen

Function BuildPattern(startArr, repeatValue, repeatCount, endArr)
    Dim newArray()
    Dim totalSize, i, j

    Dim startSize, endSize

    startSize = UBound(startArr)+1
    endSize = UBound(endArr)+1

    totalSize = startSize+repeatCount+endSize

    ReDim newArray(totalSize-1)

    j = 0

    For i = 0 To UBound(startArr)
        newArray(j) = startArr(i)
        j = j+1
    Next

    For i = 1 To repeatCount
        newArray(j) = repeatValue
        j = j+1
    Next

    For i = 0 To UBound(endArr)
        newArray(j) = endArr(i)
        j = j+1
    Next

    BuildPattern = newArray ' komischer syntax
End Function

Sub CATMain()
    Dim countRows, gap

    ' das muster der ziegelung wird hier manuell definiert

    ' man muss countRows definieren
    ' und dann die pattern (also die counts der viertel steine)
    ' die pattern werden solange wiederholt, bis countRows erreicht ist
    ' die summe der counts sollten in jeder zeile gleich sein
    ' pattern von unten nach oben

    ' 2 steht für einen halben stein
    ' 4 für einen ganzen stein

    gap = 0.15 ' die fugenbreite

    ' countRows = 11

    ' Dim pattern(1)
    ' pattern(0) = Array(4, 4, 4, 4, 1)
    ' pattern(1) = Array(2, 4, 4, 4, 3)

    ' Dim pattern(1)
    ' pattern(0) = Array(4, 2)
    ' pattern(1) = Array(2, 4)

    ' countRows = 4

    ' Dim pattern(1)
    ' pattern(0) = Array(4, 4, 4, 4, 4, 4, 4)
    ' pattern(1) = Array(2, 4, 4, 4, 4, 4, 4, 2)

    ' das ist das beispiel in den screenshots

    countRows = 10

    Dim pattern(3)
    pattern(0) = BuildPattern(Array(3), 4, 44, Array(3))
    pattern(1) = BuildPattern(Array(), 2, 91, Array())
    pattern(2) = BuildPattern(Array(3, 2), 4, 43, Array(2, 3))
    pattern(3) = BuildPattern(Array(), 2, 91, Array())

    ' das nachfolgende nicht ändern

    Dim doc As Document
    Set doc = CATIA.ActiveDocument

    Dim part As Part
    Set part = doc.Part

    If doc.Selection.Count = 1 Then
        If doc.Selection.Item(1).Type = "Sketch" Then
            Dim sketch As Sketch
            Set sketch = doc.Selection.Item(1).Value

            part.InWorkObject = sketch

            sketch.OpenEdition()

            ' Dim constraints As Constraints
            ' Set constraints = sketch.Constraints

            Dim geometries As GeometricElements
            Set geometries = sketch.GeometricElements

            Dim coords(1)
            Dim points(1, 1)

            Dim i, j

            i = 0 ' Set nur bei objekt-referenzen, nicht bei primitiven

            For Each element In sketch.GeometricElements
                If element.GeometricType = catGeoTypePoint2D Then
                    element.GetCoordinates coords

                    ' MsgBox Join(coords, ",")

                    points(i, 0) = coords(0)
                    points(i, 1) = coords(1)

                    element.Construction = True

                    i = i+1

                    If i = 2 Then
                        Exit For
                    End If
                End If
            Next

            If i <> 2 Then
                MsgBox "Exactly 2 points must be defined"
                Exit Sub
            End If

            Dim width, height

            width = Abs(points(0, 0)-points(1, 0))
            height = Abs(points(0, 1)-points(1, 1))

            ' MsgBox "height " & height & ", width " & width

            Dim originX, originY

            If points(0, 0) < points(1, 0) Then
                originX = points(0, 0)
            Else
                originX = points(1, 0)
            End If

            If points(0, 1) < points(1, 1) Then
                originY = points(0, 1)
            Else
                originY = points(1, 1)
            End If

            ' MsgBox "originX " & originX & ", originY " & originY

            Dim halfGap
            halfGap = gap/2

            Dim rowHeight
            rowHeight = (height-gap)/countRows

            ' MsgBox "rowHeight " & rowHeight

            Dim realPattern()
            ReDim realPattern(countRows-1)

            For i = 0 To countRows-1
                For j = 0 To UBound(pattern)
                    If i+j < countRows Then
                        realPattern(i+j) = pattern(j) ' Shallow Copy
                    End If
                Next
                i = i+UBound(pattern)
            Next

            Dim x, y, xA, xB, yA, yB

            Dim sumCounts, quarterWidth, brickWidth

            Dim factory As Factory2D
            Set factory = sketch.Factory2D

            Dim realPoints(3)

            For i = 0 To UBound(realPattern)
                sumCounts = 0

                For j = 0 To UBound(realPattern(i))
                    sumCounts = sumCounts+realPattern(i)(j)
                Next

                quarterWidth = (width+gap)/sumCounts

                If i <= UBound(pattern) Then
                    ' MsgBox "i " & i & ", sumCounts " & sumCounts
                End If

                y = originY+halfGap+i*rowHeight

                yA = y+halfGap
                yB = y+rowHeight-halfGap

                ' MsgBox "i " & i & ", y " & y & ", yA " & yA & ", yB " & yB

                x = originX-halfGap

                For j = 0 To UBound(realPattern(i))
                    brickWidth = realPattern(i)(j)*quarterWidth

                    xA = x+halfGap
                    xB = x+brickWidth-halfGap

                    ' CCW

                    Set realPoints(0) = factory.CreatePoint(xA, yA)
                    Set realPoints(1) = factory.CreatePoint(xB, yA)
                    Set realPoints(2) = factory.CreatePoint(xB, yB)
                    Set realPoints(3) = factory.CreatePoint(xA, yB)

                    Dim lineA As Line2D
                    Dim lineB As Line2D
                    Dim lineC As Line2D
                    Dim lineD As Line2D

                    Set lineA = factory.CreateLine(xA, yA, xB, yA)
                    Set lineB = factory.CreateLine(xB, yA, xB, yB)
                    Set lineC = factory.CreateLine(xB, yB, xA, yB)
                    Set lineD = factory.CreateLine(xA, yB, xA, yA)

                    lineA.StartPoint = realPoints(0)
                    lineA.EndPoint = realPoints(1)

                    lineB.StartPoint = realPoints(1)
                    lineB.EndPoint = realPoints(2)

                    lineC.StartPoint = realPoints(2)
                    lineC.EndPoint = realPoints(3)

                    lineD.StartPoint = realPoints(3)
                    lineD.EndPoint = realPoints(0)

                    ' wenn die linien fixiert werden sollen...

                    ' Dim constraintA As Constraint
                    ' Set constraintA = constraints.AddMonoEltCst(catCstTypeReference, lineA)
                    ' constraintA.Mode = catCstModeDrivingDimension

                    ' Dim constraintB As Constraint
                    ' Set constraintB = constraints.AddMonoEltCst(catCstTypeReference, lineB)
                    ' constraintB.Mode = catCstModeDrivingDimension

                    ' Dim constraintC As Constraint
                    ' Set constraintC = constraints.AddMonoEltCst(catCstTypeReference, lineC)
                    ' constraintC.Mode = catCstModeDrivingDimension

                    ' Dim constraintD As Constraint
                    ' Set constraintD = constraints.AddMonoEltCst(catCstTypeReference, lineD)
                    ' constraintD.Mode = catCstModeDrivingDimension

                    x = x+brickWidth
                Next
            Next

            sketch.CloseEdition()

            Dim shapeFactory As Factory
            Set shapeFactory = part.ShapeFactory

            Dim pad As Pad
            Set pad = shapeFactory.AddNewPad(sketch, gap)

            part.Update()
        Else
            MsgBox "A single sketch must be selected"
        End If
    Else
        MsgBox "A single sketch must be selected"
    End If

End Sub
